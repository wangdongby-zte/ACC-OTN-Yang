module acc-devm {
    yang-version 1.1;
    namespace "urn:ccsa:yang:acc-devm";
    prefix acc-devm;

    import ietf-yang-types {
        prefix yang;
    }

    import acc-yang-types {
        prefix acc-type;
    }

    import ietf-inet-types {
        prefix inet;
    }

    organization "xxx";
    contact "xxx";
    description "xxx";
    revision 2019-02-13 {
        description "";
        reference 
          "";
    }
    /*
    * common types
    */
    typedef operational-state {
        type enumeration {
            enum up {
                value 0;
                description "Up";
            }
            enum down {
                value 1;
                description "Down";
            }
        }
        description "Operational state";
    }
    typedef admin-state {
        type enumeration {
            enum enabled {
                value 0;
                description "Enable";
            }
            enum disabled {
                value 1;
                description "Disable";
            }
        }
        description "Admin state";
    }
    typedef laser-status {
        type enumeration {
            enum laser-on {
                description "Laser on";
            }
            enum laser-off {
                description "Laser off";
            }
            enum no-optical-module {
                description "No optical module";
            }
        }
        description "none";
    }

    typedef loopback-type {
        type enumeration {
            enum facility-loopback {
                value 0;
                description "Facility loopback";
            }
            enum terminal-loopback {
                value 1;
                description "Terminal loopback";
            }    
            enum non-loopback {
                value 2;
                description "Non loopback";
            }
        }
        description "none";
    }

    typedef interface-type {
        type enumeration {
            enum UNI {
                value 0;
                description "none";
            }
            enum NNI {
                value 1;
                description "none";
            }
        }
        description "none";
    }
    typedef service-type {
        type enumeration {
            enum ODU {
                value 0;
                description "none";
            }
            enum SDH {
                value 1;
                description "none";
            }
            enum EPL {
                value 2;
                description "none";
            }
            enum EVPL {
                value 3;
                description "none";
            }
        }
        description "none";
    }
    typedef me-status {
        type enumeration {
            enum installing {
                value 0;
                description "none";
            }
            enum running {
                value 1;
                description "none";
            }
            enum maintenance  {
                value 2;
                description "none";
            }
        }
        description "none";
    }

    typedef ntp-state {
        type enumeration {
            enum clock-never-set {
                value 0;
                description "none";
            }
            enum freq-set-from-file {
                value 1;
                description "none";
            }
            enum spike-detected {
                value 2;
                description "none";
            }
            enum frequency-mode {
                value 3;
                description "none";
            }
            enum clock-synchronized {
                value 4;
                description "none";
            }
        }
        description "rfc 5905";
    }
    typedef reset-type {
        type enumeration {
            enum soft-reset {
                value 0;
                description "Soft reset";
            }
            enum hard-reset {
                value 1;
                description "Hard reset";
            }
        }
        description "Reset type";
    }
    typedef device-type {
        type enumeration {
            enum otm-box {
                value 0;
                description "none";
            }
            enum po-box {
                value 1;
                description "none";
            }
            enum otm-pnp {
                value 2;
                description "none";
            }
            enum po-pnp {
                value 3;
                description "none";
            }
        }
        description "none";
    }

    typedef port-role {
        type enumeration {
            enum symmetric {
                value 0;
                description "";
            }
            enum root {
                value 1;
                description "";
            }
            enum leaf-node {
                value 2;
                description "";
            }
        }
    }

    typedef protect-role {
        type enumeration {
            enum null {
                value 0;
                description "";
            }
            enum protected {
                value 1;
                description "";
            }
            enum primary {
                value 2;
                description "";
            }
            enum secondary {
                value 3;
                description "";
            }
        }
    }

    /*
    * groupings
    */
    grouping state-pac {
        leaf operational-state {
            mandatory true;
            type operational-state;
            config false;
            description "Operational state";
        }
        leaf admin-state {
            mandatory true;
            type admin-state;
            description "Admin state";
        }
        description "none";
    }

    grouping ftp {
        leaf name {
            type string{
            length "1..64";
            }
                description "Name of ftp";
        }
        container state-pac {
            uses state-pac;
                description "State of ftp";
        }
        leaf layer-protocol-name {
            mandatory true;
            type identityref {
                base acc-type:layer-protocol-name;
            }
                description "Layer protocol name of ftp";
        }
        leaf-list client-ctp {
            type leafref {
                path '/acc-devm:ctps/acc-devm:ctp/acc-devm:name';
            }
                description "Client ctps";
        }
        leaf-list server-ctp {
            type leafref {
                path '/acc-devm:ctps/acc-devm:ctp/acc-devm:name';
            }
            description "Server ctps";
        }
        leaf loop-back {
            type loopback-type;
            default non-loopback;
            description "Loop back type of ftp";
        }
    }

    grouping ctp {
        leaf name {
            type string{
            length "1..64";
            }
                description "Name of ctp";
        }
        container state-pac {
            uses state-pac;
                description "State of ctp";
        }
        leaf layer-protocol-name {
            mandatory true;
            type identityref {
                base acc-type:layer-protocol-name;
            }
            description "Layer protocol name of ctp";
        }
        leaf port-role {
            type port-role;
            default symmetric;
            config false;
            description "The port role.";
        }
        leaf protect-role {
            mandatory true;
            type protect-role;
            config false;
            description "The protect role.";
        }
        leaf server-tp {
            type string{
            length "1..64";
            }
                description "Server tp";
        }
        leaf loop-back {
            type loopback-type;
            default non-loopback;
            description "Loop back type of ctp";
        }
        description "ctp";
    }
    /*
    * the data tree
    */
    container me {
        leaf name {
            type string{
              length "1..64";
            }            
            description "name";
        }
        leaf uuid {
            type string;
            config false;
            description "Universal unique identifier, MAC address is suggested.";
        }
        leaf status {
            type me-status;
            description "";
        }
        leaf manufacturer {
            mandatory true;
            type string{
              length "1..32";
            }
            config false;
            description "Manufacturer";
        }
        leaf product-name {
            mandatory true;
            type string{
              length "1..32";
            }
            config false;
            description "Product name";
        }
        leaf software-version {
            mandatory true;
            type string{
              length "1..32";
            }
            config false;
            description "Software version";
        }
        leaf hardware-version {
            mandatory true;
            type string{
              length "1..32";
            }
            config false;
            description "Hardware version";
        }
        leaf device-type {
            mandatory true;
            type device-type;
            config false;
            description "Device type";
        }
        leaf-list layer-protocol-name {
            type identityref {
                base acc-type:layer-protocol-name;
            }
            min-elements 1;
            config false;
            description "Layer protocol name";
        }
        leaf ip-address {
            mandatory true;
            type inet:ipv4-address;
            description "Ip address(ipv4)";
        }
        leaf mask {
            mandatory true;
            type yang:dotted-quad;
            description "Mask";
        }
        leaf ntp-enable {
            mandatory true;
            type boolean;
            description "Support ntp or not.";
        }
        leaf ntp-state {
            type ntp-state;
            config false;
            description "Ntp state";
        }
        container ntp-servers {
            list ntp-server {
                key 'name';
                leaf name {
                    type string {
                        length "1..32";
                    }
                    description "Name of ntp server.";
                }
                leaf ip-address {
                    mandatory true;
                    type inet:ipv4-address;
                    description "Ip address of ntp";
                }
                leaf port {
                    type inet:port-number;
                    default 123;
                    description "Port number of ntp";
                }
                leaf ntp-version {
                    type string {
                        length "1..64";
                    }
                    description "Ntp version";
                }
                description "ntp";
            }
        }
        leaf gate-way1 {
            mandatory true;
            type inet:ipv4-address;
            description "Gat way1(ipv4)";
        }
        leaf gate-way2 {
            type inet:ipv4-address;
            description "Gat way2(ipv4)";
        }
        leaf-list eq {
            type leafref {
                path '/acc-devm:eqs/acc-devm:eq/acc-devm:name';
            }
            min-elements 1;
            config false;
            description "Eq list";
        }
        description "me";
    }

    container ptps {
        list ptp {
            key 'name';
            min-elements 1;
            leaf name {
                type string{
                length "1..64";
                }
                description "Name of ptp";
            }
            container state-pac {
                uses state-pac;
                description "State of ptp";
            }
            leaf layer-protocol-name {
                mandatory true;
                type identityref {
                base acc-type:layer-protocol-name;
            }
                description "Layer protocol name of ptp";
            }
            leaf peer-ip-address {
                type string {
                    length "1..16";
                }
                config false;
                description "Peer ip address";
            }
            leaf peer-tcp-id {
                type string {
                    length "1..64";
                }
                config false;
                description "Peer ptp tcp-id";
            }
            leaf local-tcp-id {
                type string {
                    length "1..64";
                }
                config false;
                description "Local ptp tcp-id";
            }
            leaf laser-status {
                type laser-status;
                default laser-on;
                description "Laser status of ptp";
            }
            leaf-list ctp {
                type leafref {
                    path '/acc-devm:ctps/acc-devm:ctp/acc-devm:name';
                }
                description "Ctp list";
            }
            leaf interface-type {
                mandatory true;
                type interface-type;
                description "Interface type of ptp";
            }
            leaf loop-back {
                type loopback-type;
                default non-loopback;
                description "Loop back type of ptp";
            }
            container optical-power-pac {
                leaf input-power {
                    mandatory true;
                    type acc-type:real;
                    config false;
                    description "Input power of ptp";
                }
                leaf output-power {
                    mandatory true;
                    type acc-type:real;
                    description "Output power of ptp";
                }
                leaf input-power-upper-threshold {
                    mandatory true;
                    type acc-type:real;
                    config false;
                    description "Input power upper threshold of ptp";
                }
                leaf input-power-lower-threshold {
                    mandatory true;
                    type acc-type:real;
                    config false;
                    description "Input power lower threshold of ptp";
                }
                description "Optical power of ptp";
            }

            description "ptp";
        }
        description "ptps";
    }
    container ftps {
        list ftp {
            key 'name';
            uses ftp;
            description "none";
        }
        description "none";
    }    
    container ctps {
        list ctp {
            key 'name';
            uses ctp;
        }
        description "none";
    }    
    container eqs {
        list eq {
            key 'name';
            min-elements 1;
            leaf name {
                type string {
                length "1..64";
                }
                description "Name of eq";
            }
            leaf plug-state {
                mandatory true;
                type boolean;
                config false;
                description "Plug state of eq";
            }
            leaf software-version {
                mandatory true;
                type string{
                    length "1..32";
                }
                config false;
                description "Software version of eq";
            }
            leaf hardware-version {
                mandatory true;
                type string{
                    length "1..32";
                }
                config false;
                description "Hardware version of eq";
            }
            leaf-list ptp {
                type leafref {
                    path '/acc-devm:ptps/acc-devm:ptp/acc-devm:name';
                }
                min-elements 1;
                config false;
                description "Ptps of eq";
            }
            description "eq";
        }
        description "eqs";
    }

    /*
    * notifications
    */
    notification peer-change-notification {
        leaf ptp-name {
            mandatory true;
            type string {
                length 1..64;
            }
            description
                "PTP name.";
        }
        leaf peer-ip-address {
        	  mandatory true;
            type string {
                length 1..16;
            }
            description "Peer ip address";
        }
        leaf peer-ptp-name {
        	  mandatory true;
            type string {
                length 1..64;
            }
            description "Peer ptp name";
        }
        description "Peer change notification";
    } 
    
    /*
    * operations
    */
    rpc reset {
        description "reset";
        input {
            leaf eq-name {
                type string{
                  length "1..64";
                }
                description "Name of eq";
            }
            leaf reset-type {
                type reset-type;
                description "Reset type";
            }
        }
    }

    rpc modify-user-password {
        input {
            leaf old-password {
                type string {
                    length "8..16";
                }
                description "Old password.";
            }
            leaf new-password {
                type string {
                    length "8..16";
                }
                description "New password.";
            }
        }
    }
    
    rpc set-managed-element-time {
        input {
            leaf new-time {
                type yang:date-and-time;
                }
         }
    }
}
